FME workspace COULIBALY_Alou_TP2.fmw

Parameters:
- SourceDataset_CSV2 = https://donnees.montreal.ca/dataset/jardins-communautaires   # Source CSV (Comma Separated Value) File(s)
- SourceDataset_CSV2_12 = https://donnees.montreal.ca/dataset/2faa580d-d127-4a30-a79a-1ebf9d255f9b/resource/88bb6a18-54fa-4789-82e8-14888a933a4a/download/sondage-echo-donnees-2020.csv   # Source CSV (Comma Separated Value) File(s)
- SourceDataset_LAS_5 = http://depot.ville.montreal.qc.ca/geomatique/lidar_aerien/2015/299-5040_2015.laz   # Source ASPRS LAS File(s)
- SourceDataset_LAS_4 = http://depot.ville.montreal.qc.ca/geomatique/lidar_aerien/2015/298-5040_2015.laz   # Source ASPRS LAS File(s)
- SourceDataset_GEOTIFF_4 = https://donnees.montreal.ca/dataset/853eef5e-239a-447f-9352-2c8655cb7de1/resource/9b9274ca-9d40-4e8a-bd67-7ca0e19a212e/download/mnsterrainbatiment_2015_1m_plateau-mont-royal.zip   # Source GeoTIFF File(s) or URL(s)
- DestDataset_POSTGIS_9 = GEO7630H24   # Connection
- DestDataset_POSTGIS_7 = GEO7630H24   # Connection
- DestDataset_POSTGIS = GEO7630H24   # Connection
- SourceDataset_GEOTIFF = http://depot.ville.montreal.qc.ca/vues-aeriennes-1969/VM97-3_09_1969-081.TIF   # Source GeoTIFF File(s) or URL(s)
- DestDataset_POSTGIS_8 = GEO7630H24   # Connection
- DestDataset_POSTGIS_6 = GEO7630H24   # Connection
- SourceDataset_SHAPEFILE = https://donnees.montreal.ca/dataset/1c1a9b72-efaa-4484-9b19-2ab9a5561cfa/resource/56b679de-e97f-483d-9f43-1dff7eb66679/download/indice-equite-milieux-vie.zip   # Source Esri Shapefile(s)

Readers:
- CSV2_1: CSV2 from $(SourceDataset_CSV2)
- CSV2_7: CSV2 from $(SourceDataset_CSV2_12)
- LAS_2: LAS from $(SourceDataset_LAS_5)
- LAS_3: LAS from $(SourceDataset_LAS_4)
- GEOTIFF_3: GEOTIFF from $(SourceDataset_GEOTIFF_4)
- GEOTIFF_1: GEOTIFF from $(SourceDataset_GEOTIFF)
- SHAPEFILE_1: SHAPEFILE from $(SourceDataset_SHAPEFILE)

Writers:
- POSTGIS_1: POSTGIS to $(DestDataset_POSTGIS)
- POSTGIS_2: POSTGIS to $(DestDataset_POSTGIS_9)
- POSTGIS_3: POSTGIS to $(DestDataset_POSTGIS_7)
- POSTGIS_5: POSTGIS to $(DestDataset_POSTGIS_8)
- POSTGIS_4: POSTGIS to $(DestDataset_POSTGIS_6)

indice_niveau_de_vie (writer POSTGIS_3)
    attributes: adidu varchar(254), arr_ville varchar(254), type varchar(254), pop2021 int4, mono_pr float8, pr_men_bil float8, pr_ind_mpc float8, pr_nocanop float8, nb_pass_tc float8, acp_econo float8, indice_emv int4, log_priv20 int4, imm_recent float8, autoch_min float8, sans_diplo float8, pr_log_aut float8, pr_laeq60p float8, pr_indust3 float8, pr_logchal float8, mefaits_po float8, collisions float8, crimes_pon float8, nb_commerc float8, nb_organis float8, nb_pharmac float8, nb_ecoles_ float8, nb_emplois int4, nb_biblio_ float8, nb_equipem float8, superficie float8,
      acp_social float8, acp_enviro float8, acp_securi float8, acp_proxim float8, acp_cultsp float8, acp_soci_1 int4, acp_econo_ int4, acp_envi_1 int4, acp_secu_1 int4, acp_prox_1 int4, acp_cult_1 int4
ContourGenerator__Rejected_: Logger
    LOG_FEATURE = LOG_ONLY
    MAXCOORDS = 20
    MAXFEATS = 20
    MESSAGE = Feature is:
    SEVERITY = INFO
EsriReprojector
    DEST = ESRIWKT|WGS_1984_Web_Mercator_Auxiliary_Sphere|PROJCS["WGS_1984_Web_Mercator_Auxiliary_Sphere",GEOGCS["GCS_WGS_1984",DATUM["D_WGS_1984",SPHEROID["WGS_1984",6378137.0,298.257223563]],PRIMEM["Greenwich",0.0],UNIT["Degree",0.0174532925199433]],PROJECTION["Mercator_Auxiliary_Sphere"],PARAMETER["False_Easting",0.0],PARAMETER["False_Northing",0.0],PARAMETER["Central_Meridian",0.0],PARAMETER["Standard_Parallel_1",0.0],PARAMETER["Auxiliary_Sphere_Type",0.0],UNIT["Meter",1.0]]
    GEOTRANSFORMATION_NAME = NAD_1983_CSRS_To_WGS_1984
    INTERPOLATION_TYPE_NAME = Nearest Neighbor
    RASTER_CELL_SIZE = Preserve Cells
    RASTER_TOLERANCE = 0.0
    SOURCE = ESRIWKT|NAD_1983_CSRS_MTM_8|PROJCS["NAD_1983_CSRS_MTM_8",GEOGCS["GCS_North_American_1983_CSRS",DATUM["D_North_American_1983_CSRS",SPHEROID["GRS_1980",6378137.0,298.257222101]],PRIMEM["Greenwich",0.0],UNIT["Degree",0.0174532925199433]],PROJECTION["Transverse_Mercator"],PARAMETER["False_Easting",304800.0],PARAMETER["False_Northing",0.0],PARAMETER["Central_Meridian",-73.5],PARAMETER["Scale_Factor",0.9999],PARAMETER["Latitude_Of_Origin",0.0],UNIT["Meter",1.0]]
    REPROJECTED -> SurfaceModeller [POINTS/LINES]
AreaBuilder_2__Rejected_: Logger
    LOG_FEATURE = LOG_ONLY
    MAXCOORDS = 20
    MAXFEATS = 20
    MESSAGE = Feature is:
    SEVERITY = INFO
SurfaceModeller__Rejected_: Logger
    LOG_FEATURE = LOG_ONLY
    MAXCOORDS = 20
    MAXFEATS = 20
    MESSAGE = Feature is:
    SEVERITY = INFO
PointCloudCombiner__Rejected_: Logger
    LOG_FEATURE = LOG_ONLY
    MAXCOORDS = 20
    MAXFEATS = 20
    MESSAGE = Feature is:
    SEVERITY = INFO

Bookmark: Importation Sondage écho sur l'inclusion des personnes immigrantes
CSV (reader CSV2_7)
    attributes: record uint32, date varchar(16), sexe uint32, age uint32, ARRON uint32, NAISS uint32, NAISSANCE2 varchar(34), NAIS2r9 uint32, LANGU uint32, LANGUr96oe varchar(32), LGBTQ uint32, MINO uint32, MINO2 uint32, SCOL uint32, SCOL2 uint32, SCOL3 uint32, SCOL2r1oe varchar(52), SCOL2r2oe varchar(34), Q1 uint32, Q2r1 uint32, Q2r2 uint32, Q2r3 uint32, Q2r4 uint32, Q2r5 uint32, Q2r6 uint32, Q2r7 uint32, Q2r8 uint32, FOY1 uint32, FOY1_r1 uint32, FOY1_r99 uint32,
      APPAR1 uint32, APP1_r97 uint32, APP1_r99 uint32, ENFAN uint32, CHARGE uint32, CHAR_r0 uint32, CHAR_r99 uint32, Q3r1 uint32, Q4 uint32, Q5 uint32, Q5O uint32, Q6 uint32, Q7 uint32, Q7O uint32, OCCUP uint32, Q10 uint32, Q11 uint32, Q13 uint32, Q14 uint32, Q15r1 uint32, Q16 uint32, Q17r1 uint32, Q17r2 uint32, Q17r3 uint32, Q17r4 uint32, Q17r5 uint32, Q17r6 uint32, Q17r97 uint32, Q17r98 uint32, Q17r99 uint32,
      Q18Ar1 uint32, Q18Ar2 uint32, Q18Ar3 uint32, Q18Ar4 uint32, Q18Ar5 uint32, Q18Ar6 uint32, Q18Ar96 uint32, Q18Ar97 uint32, Q18Ar98 uint32, Q18Ar99 uint32, Q18B uint32, REVEN uint32, REVEN2 uint32, Q19 uint32, Q19_r0 uint32, Q20r1 uint32, Q20r2 uint32, Q20r3 uint32, Q20r4 uint32, Q20r5 uint32, Q20r6 uint32, Q20r7 uint32, Q20r8 uint32, Q20r9 uint32, Q20r96 uint32, Q20r97 uint32, Q20r98 uint32, Q20r99 uint32, Q21 uint32, Q22r1 uint32,
      Q22r2 uint32, Q22r3 uint32, Q22r4 uint32, Q22r5 uint32, Q22r6 uint32, Q22r7 uint32, Q22r8 uint32, Q22r96 uint32, Q22r97 uint32, Q22r98 uint32, Q22r99 uint32, Q23r1 uint32, Q23r2 uint32, Q23r3 uint32, Q23r4 uint32, Q23r5 uint32, Q23r6 uint32, Q23r7 uint32, Q23r8 uint32, Q23r9 uint32, Q23r96 uint32, Q23r97 uint32, Q23r98 uint32, Q23r99 uint32, Q24r1 uint32, Q24r2 uint32, Q24r3 uint32, Q24r4 uint32, Q24r5 uint32, Q24r6 uint32,
      Q24r7 uint32, Q24r8 uint32, Q24r96 uint32, Q24r97 uint32, Q24r98 uint32, Q24r99 uint32, Q25 uint32, Q26 uint32, Q27 uint32, PROP uint32, Q28 uint32, Q29 uint32, Q30 uint32, Q31r1 uint32, Q31_r0 uint32, Q32 uint32, Q33r1 uint32, Q33r2 uint32, Q33r3 uint32, Q33r4 uint32, Q33r5 uint32, Q33r6 uint32, Q33r97 uint32, Q34r1 uint32, Q34_r0 uint32, Q35r1 uint32, Q35r2 uint32, Q35r3 uint32, Q35r4 uint32, Q35r5 uint32,
      Q35r6 uint32, Q36r1 uint32, Q36r2 uint32, Q36r3 uint32, Q36r4 uint32, Q36r5 uint32, Q36r6 uint32, Q36r7 uint32, Q36r8 uint32, Q36r96 uint32, Q36r97 uint32, Q36r98 uint32, Q36r99 uint32, Q37 uint32, Q38r1 uint32, Q38r2 uint32, Q38r3 uint32, Q38r4 uint32, Q38r5 uint32, Q38r6 uint32, Q38r7 uint32, Q38r8 uint32, Q38r9 uint32, Q38r96 uint32, Q38r98 uint32, Q38r99 uint32, Q39r1 uint32, Q39_r0 uint32, Q40r1 uint32, Q40_r0 uint32,
      Q41 uint32, Q42 uint32, Q43 uint32, Q44 uint32, Q45 uint32, Q46 uint32, Q47 uint32, Q47B uint32, Q48 uint32, Q49r1 uint32, Q49r2 uint32, Q49r3 uint32, Q49r4 uint32, Q49r97 uint32, Q49r98 uint32, Q49r99 uint32, Q50r1 uint32, Q50r2 uint32, Q50r3 uint32, Q50r4 uint32, Q50r96 uint32, Q50r97 uint32, Q50r98 uint32, Q50r99 uint32, Q51A uint32, Q51Br2 uint32, Q51Br3 uint32, Q51Br4 uint32, Q51Br5 uint32, Q51Br6 uint32,
      Q51Br96 uint32, Q51Br97 uint32, Q51Br98 uint32, Q51Br99 uint32, Q52r1 uint32, Q52r2 uint32, Q52r3 uint32, Q52r4 uint32, Q52r5 uint32, Q52r6 uint32, Q52r7 uint32, Q52r8 uint32, Q52r9 uint32, Q52r96 uint32, Q53r1 uint32, Q53r2 uint32, Q53r3 uint32, Q53r4 uint32, Q53r5 uint32, Q53r6 uint32, Q53r7 uint32, Q53r8 uint32, Q53r96 uint32, Q53r98 uint32, Q53r99 uint32, Q54r1 uint32, Q54r2 uint32, Q54r3 uint32, Q54r4 uint32, Q54r5 uint32,
      Q54r6 uint32, Q54r96 uint32, Q54_r98 uint32, Q54_r99 uint32, Q54Top1 uint32, Q55r1 uint32, Q55r2 uint32, Q55r3 uint32, Q56 uint32, Q56_r0 uint32, Q57r1 uint32, Q57r2 uint32, Q57r3 uint32, Q57r4 uint32, Q57r5 uint32, Q57r6 uint32, Q57r7 uint32, Q57r8 uint32, Q57r9 uint32, Q57r10 uint32, Q57r96 uint32, Q57r98 uint32, Q57r99 uint32, Q58r1 uint32, Q58r2 uint32, Q58r3 uint32, Q58r4 uint32, Q58r5 uint32, Q58r6 uint32, Q58r96 uint32,
      Q58r98 uint32, Q58r99 uint32, Q58X uint32, Q59r1 uint32, Q59r2 uint32, Q59r3 uint32, Q59r4 uint32, Q59r5 uint32, Q59r6 uint32, Q59r7 uint32, Q59r8 uint32, Q59r9 uint32, Q59r10 uint32, Q59r11 uint32, Q59r12 uint32, Q60 uint32, Q61r1 uint32, Q61r2 uint32, Q61r3 uint32, Q61r4 uint32, Q61r5 uint32, Q61r6 uint32, Q61r7 uint32, Q61r8 uint32, Q61r9 uint32, Q61r10 uint32, Q61r96 uint32, Q61r98 uint32, Q61r99 uint32, Q62 uint32,
      Q63 uint32, Q64 uint32, Q65r1 uint32, Q65r2 uint32, Q65r3 uint32, Q65r4 uint32, Q65r5 uint32, Q65r6 uint32, Q65r7 uint32, Q65r8 uint32, Q65r9 uint32, Q65r10 uint32, Q65r11 uint32, Q65r98 uint32, Q65r99 uint32, Q66 uint32, Q67 uint32, Q68r1 uint32, Q68r2 uint32, Q68r3 uint32, Q68r4 uint32, Q68r5 uint32, Q68r6 uint32, Q68r7 uint32, Q68r8 uint32, Q68r9 uint32, Q68r10 uint32, Q68r11 uint32, Q68r98 uint32, Q68r99 uint32,
      Q69 uint32, Q70 uint32, Q71r1 uint32, Q71r2 uint32, Q71r3 uint32, Q71r4 uint32, Q71r5 uint32, Q71r6 uint32, Q71r7 uint32, Q71r8 uint32, Q71r9 uint32, Q71r10 uint32, Q71r11 uint32, Q71r98 uint32, Q71r99 uint32, Q72 uint32, Q73 uint32, Q74 uint32, Q75 uint32, Q76r1 uint32, Q76r2 uint32, Q76r3 uint32, Q76r4 uint32, Q76r5 uint32, Q76r6 uint32, Q76r7 uint32, Q76r96 uint32, Q76r98 uint32, Q76r99 uint32, Q77 uint32,
      weight real32
    -> Reprojector_3

Bookmark: Reproection en 3857
Reprojector_3
    DEST = EPSG:3857
    INTERPOLATION_TYPE_NAME = Nearest Neighbor
    RASTER_CELL_SIZE = Preserve Cells
    RASTER_TOLERANCE = 0.0
    REPROJECTED -> StatisticsCalculator
    REPROJECTED -> StatisticsCalculator_2
    REPROJECTED -> StatisticsCalculator_9
    REPROJECTED -> StatisticsCalculator_10
    REPROJECTED -> StatisticsCalculator_11
    REPROJECTED -> StatisticsCalculator_12
    REPROJECTED -> StatisticsCalculator_13
    REPROJECTED -> StatisticsCalculator_14
Reprojector_2
    DEST = EPSG:3857
    INTERPOLATION_TYPE_NAME = Nearest Neighbor
    RASTER_CELL_SIZE = Preserve Cells
    RASTER_TOLERANCE = 0.0
    REPROJECTED -> AttributeManager
Reprojector_5
    DEST = EPSG:3857
    INTERPOLATION_TYPE_NAME = Nearest Neighbor
    RASTER_CELL_SIZE = Preserve Cells
    RASTER_TOLERANCE = 0.0
    REPROJECTED -> RasterPropertyExtractor
    REPROJECTED -> RasterResampler
Reprojector_6
    DEST = EPSG:3857
    INTERPOLATION_TYPE_NAME = Nearest Neighbor
    RASTER_CELL_SIZE = Preserve Cells
    RASTER_TOLERANCE = 0.0
    REPROJECTED -> ContourGenerator [POINTS/LINES]

Bookmark: Analyse différenciée selon le sexe
StatisticsCalculator
    ATTR_ACCUM_MODE = None
    CALCULATION_MODE = NUMERIC
    FEAT_STATS = sexe,NUMERIC_MODE,,,COUNT,,,,,,,,,,HIST;age,NUMERIC_MODE,,,,,,,,,,,,,;ARRON,NUMERIC_MODE,,,,,,,,,,,,,;LANGUr96oe,NUMERIC_MODE,,,,,,,,,,,,,;NAISS,NUMERIC_MODE,,,,,,,,,,,,,;NAISSANCE2,NUMERIC_MODE,,,,,,,,,,,,,;MINO,NUMERIC_MODE,,,,,,,,,,,,,;OCCUP,NUMERIC_MODE,,,,,,,,,,,,,;PROP,NUMERIC_MODE,,,,,,,,,,,,,;REVEN,NUMERIC_MODE,,,,,,,,,,,,,;Q3r1,NUMERIC_MODE,,,,,,,,,,,,,;Q4,NUMERIC_MODE,,,,,,,,,,,,,;MINO2,NUMERIC_MODE,,,,,,,,,,,,,
    GROUP_BY = sexe NAISS
    SUMMARY -> FeatureJoiner [RIGHT]

Bookmark: Analyse différencié selon le statut d'immigration
StatisticsCalculator_2
    ATTR_ACCUM_MODE = None
    CALCULATION_MODE = NUMERIC
    FEAT_STATS = NAISS,NUMERIC_MODE,,,COUNT,,,,,,,,,,;age,NUMERIC_MODE,,,,,,,,,,,,,;ARRON,NUMERIC_MODE,,,,,,,,,,,,,;LANGUr96oe,NUMERIC_MODE,,,,,,,,,,,,,;MINO,NUMERIC_MODE,,,,,,,,,,,,,;ENFAN,NUMERIC_MODE,,,,,,,,,,,,,;CHARGE,NUMERIC_MODE,,,,,,,,,,,,,;OCCUP,NUMERIC_MODE,,,,,,,,,,,,,;PROP,NUMERIC_MODE,,,,,,,,,,,,,;REVEN,NUMERIC_MODE,,,,,,,,,,,,,;MINO2,NUMERIC_MODE,,,,,,,,,,,,,;Q4,NUMERIC_MODE,,,,,,,,,,,,,;Q3r1,NUMERIC_MODE,,,,,,,,,,,,,;sexe,NUMERIC_MODE,,,,,,,,,,,,,
    GROUP_BY = NAISS sexe
    SUMMARY -> FeatureJoiner_2 [RIGHT]

Bookmark: Analyse différencié selon l'appartenance à une minorité
StatisticsCalculator_11
    ATTR_ACCUM_MODE = None
    CALCULATION_MODE = NUMERIC
    FEAT_STATS = sexe,NUMERIC_MODE,,,,,,,,,,,,,;age,NUMERIC_MODE,,,,,,,,,,,,,;ARRON,NUMERIC_MODE,,,,,,,,,,,,,;LANGUr96oe,NUMERIC_MODE,,,,,,,,,,,,,;NAISS,NUMERIC_MODE,,,,,,,,,,,,,;NAISSANCE2,NUMERIC_MODE,,,,,,,,,,,,,;MINO,NUMERIC_MODE,,,,,,,,,,,,,;OCCUP,NUMERIC_MODE,,,,,,,,,,,,,;PROP,NUMERIC_MODE,,,,,,,,,,,,,;REVEN,NUMERIC_MODE,,,,,,,,,,,,,;Q3r1,NUMERIC_MODE,,,,,,,,,,,,,;Q4,NUMERIC_MODE,,,,,,,,,,,,,;MINO2,NUMERIC_MODE,,,COUNT,,,,,,,,,,
    GROUP_BY = NAISS sexe MINO2
    SUMMARY -> FeatureJoiner_4 [RIGHT]

Bookmark: Analyse selon le lieu de Naissance
StatisticsCalculator_14
    ATTR_ACCUM_MODE = None
    CALCULATION_MODE = NUMERIC
    FEAT_STATS = sexe,NUMERIC_MODE,,,,,,,,,,,,,;age,NUMERIC_MODE,,,,,,,,,,,,,;ARRON,NUMERIC_MODE,,,,,,,,,,,,,;LANGUr96oe,NUMERIC_MODE,,,,,,,,,,,,,;NAISS,NUMERIC_MODE,,,,,,,,,,,,,;NAISSANCE2,NUMERIC_MODE,,,COUNT,,,,,,,,,,;MINO,NUMERIC_MODE,,,,,,,,,,,,,;OCCUP,NUMERIC_MODE,,,,,,,,,,,,,;PROP,NUMERIC_MODE,,,,,,,,,,,,,;REVEN,NUMERIC_MODE,,,,,,,,,,,,,;Q3r1,NUMERIC_MODE,,,,,,,,,,,,,;Q4,NUMERIC_MODE,,,,,,,,,,,,,;MINO2,NUMERIC_MODE,,,,,,,,,,,,,
    GROUP_BY = NAISS sexe NAISSANCE2
    SUMMARY -> FeatureJoiner_6 [RIGHT]

Bookmark: Analyse différenciée selon l'âge
StatisticsCalculator_9
    ATTR_ACCUM_MODE = None
    CALCULATION_MODE = NUMERIC
    FEAT_STATS = sexe,NUMERIC_MODE,,,,,,,,,,,,,;age,NUMERIC_MODE,,,COUNT,,,,,,,,,,;ARRON,NUMERIC_MODE,,,,,,,,,,,,,;LANGUr96oe,NUMERIC_MODE,,,,,,,,,,,,,;NAISS,NUMERIC_MODE,,,,,,,,,,,,,;NAISSANCE2,NUMERIC_MODE,,,,,,,,,,,,,;MINO,NUMERIC_MODE,,,,,,,,,,,,,;OCCUP,NUMERIC_MODE,,,,,,,,,,,,,;PROP,NUMERIC_MODE,,,,,,,,,,,,,;REVEN,NUMERIC_MODE,,,,,,,,,,,,,;Q3r1,NUMERIC_MODE,,,,,,,,,,,,,;Q4,NUMERIC_MODE,,,,,,,,,,,,,;MINO2,NUMERIC_MODE,,,,,,,,,,,,,
    GROUP_BY = age sexe NAISS
    SUMMARY -> FeatureJoiner [LEFT]

Bookmark: Jointure des entités
FeatureJoiner
    ATTR_CONFLICT_RES = Prefer Left
    GEOMETRY_HANDLING = Prefer Left
    JOIN_KEYS = age.total_count sexe.total_count AUTO
    JOIN_MODE = Full
    JOINED -> FeatureJoiner_2 [LEFT]
    <REJECTED> -> FeatureJoiner__Rejected_
FeatureJoiner__Rejected_: Logger
    LOG_FEATURE = LOG_ONLY
    MAXCOORDS = 20
    MAXFEATS = 20
    MESSAGE = Feature is:
    SEVERITY = INFO
FeatureJoiner_2
    ATTR_CONFLICT_RES = Prefer Left
    GEOMETRY_HANDLING = Prefer Left
    JOIN_KEYS = age.total_count NAISS.total_count AUTO sexe.total_count NAISS.total_count AUTO
    JOIN_MODE = Full
    JOINED -> FeatureJoiner_3 [LEFT]
    <REJECTED> -> FeatureJoiner_2__Rejected_
FeatureJoiner_2__Rejected_: Logger
    LOG_FEATURE = LOG_ONLY
    MAXCOORDS = 20
    MAXFEATS = 20
    MESSAGE = Feature is:
    SEVERITY = INFO
FeatureJoiner_3
    ATTR_CONFLICT_RES = Prefer Left
    GEOMETRY_HANDLING = Prefer Left
    JOIN_KEYS = age.total_count LANGUr96oe.total_count AUTO sexe.total_count LANGUr96oe.total_count AUTO NAISS.total_count LANGUr96oe.total_count AUTO
    JOIN_MODE = Full
    JOINED -> FeatureJoiner_4 [LEFT]
    <REJECTED> -> FeatureJoiner_3__Rejected_
FeatureJoiner_3__Rejected_: Logger
    LOG_FEATURE = LOG_ONLY
    MAXCOORDS = 20
    MAXFEATS = 20
    MESSAGE = Feature is:
    SEVERITY = INFO
FeatureJoiner_4
    ATTR_CONFLICT_RES = Prefer Left
    GEOMETRY_HANDLING = Prefer Left
    JOIN_KEYS = age.total_count MINO2.total_count AUTO sexe.total_count MINO2.total_count AUTO LANGUr96oe.total_count MINO2.total_count AUTO NAISS.total_count MINO2.total_count AUTO
    JOIN_MODE = Full
    JOINED -> FeatureJoiner_5 [LEFT]
    <REJECTED> -> FeatureJoiner_4__Rejected_
FeatureJoiner_4__Rejected_: Logger
    LOG_FEATURE = LOG_ONLY
    MAXCOORDS = 20
    MAXFEATS = 20
    MESSAGE = Feature is:
    SEVERITY = INFO
FeatureJoiner_5
    ATTR_CONFLICT_RES = Prefer Left
    GEOMETRY_HANDLING = Prefer Left
    JOIN_KEYS = age.total_count OCCUP.total_count AUTO LANGUr96oe.total_count OCCUP.total_count AUTO MINO2.total_count OCCUP.total_count AUTO NAISS.total_count OCCUP.total_count AUTO sexe.total_count OCCUP.total_count AUTO
    JOIN_MODE = Full
    JOINED -> FeatureJoiner_6 [LEFT]
    <REJECTED> -> FeatureJoiner_5__Rejected_
FeatureJoiner_5__Rejected_: Logger
    LOG_FEATURE = LOG_ONLY
    MAXCOORDS = 20
    MAXFEATS = 20
    MESSAGE = Feature is:
    SEVERITY = INFO
FeatureJoiner_6
    ATTR_CONFLICT_RES = Prefer Left
    GEOMETRY_HANDLING = Prefer Left
    JOIN_KEYS = age.total_count NAISSANCE2.total_count AUTO LANGUr96oe.total_count NAISSANCE2.total_count AUTO MINO2.total_count NAISSANCE2.total_count AUTO NAISS.total_count NAISSANCE2.total_count AUTO OCCUP.total_count NAISSANCE2.total_count AUTO sexe.total_count NAISSANCE2.total_count AUTO
    JOIN_MODE = Full
    JOINED -> FeatureJoiner_7 [LEFT]
    <REJECTED> -> FeatureJoiner_6__Rejected_
FeatureJoiner_6__Rejected_: Logger
    LOG_FEATURE = LOG_ONLY
    MAXCOORDS = 20
    MAXFEATS = 20
    MESSAGE = Feature is:
    SEVERITY = INFO
FeatureJoiner_7
    ATTR_CONFLICT_RES = Prefer Left
    GEOMETRY_HANDLING = Prefer Left
    JOIN_KEYS = age.total_count REVEN.total_count AUTO LANGUr96oe.total_count REVEN.total_count AUTO MINO2.total_count REVEN.total_count AUTO NAISS.total_count REVEN.total_count AUTO NAISSANCE2.total_count REVEN.total_count AUTO sexe.total_count REVEN.total_count AUTO
    JOIN_MODE = Full
    JOINED -> sondage_immigrant (writer POSTGIS_2)
    <REJECTED> -> FeatureJoiner_7__Rejected_
FeatureJoiner_7__Rejected_: Logger
    LOG_FEATURE = LOG_ONLY
    MAXCOORDS = 20
    MAXFEATS = 20
    MESSAGE = Feature is:
    SEVERITY = INFO

Bookmark: Analyse différencié selon la langue
StatisticsCalculator_10
    ATTR_ACCUM_MODE = None
    CALCULATION_MODE = NUMERIC
    FEAT_STATS = sexe,NUMERIC_MODE,,,,,,,,,,,,,;age,NUMERIC_MODE,,,,,,,,,,,,,;ARRON,NUMERIC_MODE,,,,,,,,,,,,,;LANGUr96oe,NUMERIC_MODE,,,COUNT,,,,,,,,,,;NAISS,NUMERIC_MODE,,,,,,,,,,,,,;NAISSANCE2,NUMERIC_MODE,,,,,,,,,,,,,;MINO,NUMERIC_MODE,,,,,,,,,,,,,;OCCUP,NUMERIC_MODE,,,,,,,,,,,,,;PROP,NUMERIC_MODE,,,,,,,,,,,,,;REVEN,NUMERIC_MODE,,,,,,,,,,,,,;Q3r1,NUMERIC_MODE,,,,,,,,,,,,,;Q4,NUMERIC_MODE,,,,,,,,,,,,,;MINO2,NUMERIC_MODE,,,,,,,,,,,,,
    GROUP_BY = NAISS sexe LANGUr96oe
    SUMMARY -> FeatureJoiner_3 [RIGHT]

Bookmark: Analyse differencié selon le statut d'occupation
StatisticsCalculator_12
    ATTR_ACCUM_MODE = None
    CALCULATION_MODE = NUMERIC
    FEAT_STATS = sexe,NUMERIC_MODE,,,,,,,,,,,,,;age,NUMERIC_MODE,,,,,,,,,,,,,;ARRON,NUMERIC_MODE,,,,,,,,,,,,,;LANGUr96oe,NUMERIC_MODE,,,,,,,,,,,,,;NAISS,NUMERIC_MODE,,,,,,,,,,,,,;NAISSANCE2,NUMERIC_MODE,,,,,,,,,,,,,;MINO,NUMERIC_MODE,,,,,,,,,,,,,;OCCUP,NUMERIC_MODE,,,COUNT,,,,,,,,,,;PROP,NUMERIC_MODE,,,,,,,,,,,,,;REVEN,NUMERIC_MODE,,,,,,,,,,,,,;Q3r1,NUMERIC_MODE,,,,,,,,,,,,,;Q4,NUMERIC_MODE,,,,,,,,,,,,,;MINO2,NUMERIC_MODE,,,,,,,,,,,,,
    GROUP_BY = NAISS sexe OCCUP
    SUMMARY -> FeatureJoiner_5 [RIGHT]

Bookmark: Analyse différencié selon le revenu
StatisticsCalculator_13
    ATTR_ACCUM_MODE = None
    CALCULATION_MODE = NUMERIC
    FEAT_STATS = sexe,NUMERIC_MODE,,,,,,,,,,,,,;age,NUMERIC_MODE,,,,,,,,,,,,,;ARRON,NUMERIC_MODE,,,,,,,,,,,,,;LANGUr96oe,NUMERIC_MODE,,,,,,,,,,,,,;NAISS,NUMERIC_MODE,,,,,,,,,,,,,;NAISSANCE2,NUMERIC_MODE,,,,,,,,,,,,,;MINO,NUMERIC_MODE,,,,,,,,,,,,,;OCCUP,NUMERIC_MODE,,,,,,,,,,,,,;PROP,NUMERIC_MODE,,,,,,,,,,,,,;REVEN,NUMERIC_MODE,,,COUNT,,,,,,,,,,;Q3r1,NUMERIC_MODE,,,,,,,,,,,,,;Q4,NUMERIC_MODE,,,,,,,,,,,,,;MINO2,NUMERIC_MODE,,,,,,,,,,,,,
    GROUP_BY = NAISS sexe REVEN
    SUMMARY -> FeatureJoiner_7 [RIGHT]

Bookmark: Resultat en Postgis
sondage_immigrant (writer POSTGIS_2)
    attributes: sexe int8, age int8, naiss int8, age_total_count numeric(20,0), sexe_total_count numeric(20,0), sexe_histogram{}_count numeric(20,0), sexe_histogram{}_value int8, naiss_total_count numeric(20,0), langur96oe varchar(32), langur96oe_total_count numeric(20,0), mino2 int8, mino2_total_count numeric(20,0), occup int8, occup_total_count numeric(20,0), naissance2 varchar(34), naissance2_total_count numeric(20,0), reven int8, reven_total_count numeric(20,0)

Bookmark: Importaion Indices d'équité des milieux de vie
IEMV_20230731_MTM32188 (reader SHAPEFILE_1)
    attributes: adidu varchar(254), arr_ville varchar(254), type varchar(254), pop2021 long, log_priv20 long, mono_pr double, imm_recent double, autoch_min double, sans_diplo double, pr_men_bil double, pr_ind_mpc double, pr_log_aut double, pr_laeq60p double, pr_nocanop double, pr_indust3 double, pr_logchal double, mefaits_po double, collisions double, crimes_pon double, nb_commerc double, nb_organis double, nb_pharmac double, nb_ecoles_ double, nb_pass_tc double, nb_emplois long, nb_biblio_ double, nb_equipem double, superficie double, ACP_social double, ACP_econo double,
      ACP_enviro double, ACP_securi double, ACP_proxim double, ACP_CultSp double, ACP_soci_1 long, ACP_econo_ long, ACP_envi_1 long, ACP_secu_1 long, ACP_prox_1 long, ACP_Cult_1 long, Indice_emv long
    -> Reprojector_2

Bookmark: Retirer certaines variables
AttributeManager
    ATTR_TABLE:
      REMOVE mefaits_pond (real64)
      REMOVE collisions_rt (real64)
      REMOVE crimes_pond (real64)
    -> indice_niveau_de_vie (writer POSTGIS_3)

Bookmark: Importation Image aérienne Mont Royal
GEOTIFF (reader GEOTIFF_1)
    -> Reprojector_5

Bookmark: Extraction des métadonnées du raster
RasterPropertyExtractor
    <REJECTED> -> RasterPropertyExtractor__Rejected_
RasterPropertyExtractor__Rejected_: Logger
    LOG_FEATURE = LOG_ONLY
    MAXCOORDS = 20
    MAXFEATS = 20
    MESSAGE = Feature is:
    SEVERITY = INFO

Bookmark: Rééchantillonage de l'image raster
RasterResampler
    COLUMNS = 8128/2
    INTERPOLATION_TYPE_NAME = Nearest Neighbor
    ROWCOL_OR_CELLSIZE = RowsColumns
    ROWS = 8893/2
    RESAMPLED -> WebMapTiler
    <REJECTED> -> RasterResampler__Rejected_
RasterResampler__Rejected_: Logger
    LOG_FEATURE = LOG_ONLY
    MAXCOORDS = 20
    MAXFEATS = 20
    MESSAGE = Feature is:
    SEVERITY = INFO

Bookmark: Création de tuile vectorielle
WebMapTiler
    INTERPOLATION_TYPE_NAME = Nearest Neighbor
    NUM_TILES_ATTRIBUTE = _num_tiles
    QUADKEY_ATTRIBUTE = _quadkey
    RASTER_INDEX_ATTRIBUTE = _raster_index
    TILE_COLUMN_ATTRIBUTE = _tile_column
    TILE_ROW_ATTRIBUTE = _tile_row
    TILE_SCHEME = GoogleMapsCompatible
    ZOOM_LEVEL_ATTRIBUTE = _zoom_level
    TILES -> image (writer POSTGIS_4)

Bookmark: Résultat en postgis
image (writer POSTGIS_4)
    attributes: _quadkey varchar, _zoom_level numeric(20,0), _tile_column numeric(20,0), _tile_row numeric(20,0), _raster_index numeric(20,0), _num_tiles numeric(20,0)

Bookmark: Importation MNS Plateau Mont Royal
GEOTIFF (reader GEOTIFF_3)
    -> Reprojector_6

Bookmark: Création ligne de contour
ContourGenerator
    CONTOUR_DIMENSION = 3
    CONTOUR_INTERVAL = 25
    ELEV_ATTR = _elevation
    IGNORE_INPUT_ON_INTERVAL = Perturb Input Points On Contour Interval
    TOLERANCE = 0
    CONTOURS -> Generalizer
    <REJECTED> -> ContourGenerator__Rejected_

Bookmark: Lissage des géométries
Generalizer
    ALG_TEXT = Douglas (Generalize)
    PRESERVE = No
    PRESERVE_PATHS = No
    TOLERANCE = 10
    -> AreaBuilder
    <REJECTED> -> Generalizer__Rejected_
Generalizer__Rejected_: Logger
    LOG_FEATURE = LOG_ONLY
    MAXCOORDS = 20
    MAXFEATS = 20
    MESSAGE = Feature is:
    SEVERITY = INFO

Bookmark: Création de polygones
AreaBuilder
    ALLOW_CYCLES = No
    CHECK_CURVE_DIRECTION = No
    CONNECT_Z_MODE = First Wins
    CONSIDER_NODE_ELEVATION = no
    DEAGGREGATE_INPUT = Deaggregate
    DONUT_CREATION = YES
    DROP_HOLES = No
    LINES_AS_SEGMENTS = No
    POLY_ACCUM_ATTRS_NAME = Use Attributes From One Feature
    SNAPTYPE_PARAM = None
    AREA -> contour_polygones (writer POSTGIS_1)
    <REJECTED> -> AreaBuilder__Rejected_
AreaBuilder__Rejected_: Logger
    LOG_FEATURE = LOG_ONLY
    MAXCOORDS = 20
    MAXFEATS = 20
    MESSAGE = Feature is:
    SEVERITY = INFO

Bookmark: Résultat en postgis
contour_polygones (writer POSTGIS_1)
    attributes: _elevation float8

Bookmark: Importation Nuage de points lidar
LAS (reader LAS_2)
    -> PointCloudThinner_2
LAS (reader LAS_3)
    -> PointCloudThinner_3

Bookmark: Réduction nombre de points avec un filtre de 100
PointCloudThinner_2
    INTERVAL = 100
    THINNED -> PointCloudCombiner
    <REJECTED> -> PointCloudThinner_2__Rejected_
PointCloudThinner_2__Rejected_: Logger
    LOG_FEATURE = LOG_ONLY
    MAXCOORDS = 20
    MAXFEATS = 20
    MESSAGE = Feature is:
    SEVERITY = INFO
PointCloudThinner_3
    INTERVAL = 100
    THINNED -> PointCloudCombiner
    <REJECTED> -> PointCloudThinner_3__Rejected_
PointCloudThinner_3__Rejected_: Logger
    LOG_FEATURE = LOG_ONLY
    MAXCOORDS = 20
    MAXFEATS = 20
    MESSAGE = Feature is:
    SEVERITY = INFO

Bookmark: Combine tous les nuages en un seul
PointCloudCombiner
    ACCUM_ATTRS_NAME = Yes
    EXTRACT_RASTER_NODATA_NAME = No
    SPACING = 1.0
    -> EsriReprojector
    <REJECTED> -> PointCloudCombiner__Rejected_

Bookmark: Créeation mns
SurfaceModeller
    ADDZ_TYPE = Replace Z
    CONTOUR_DIMENSION = 3
    CONTOUR_INTERVAL = 100.0
    DRAPE_TYPE = VERTEX
    IGNORE_INPUT_ON_INTERVAL = Perturb Input Points On Contour Interval
    INTERPOLATION_TYPE = AUTO
    NODATA_VALUE = -32767.0
    TOLERANCE = 10
    X_SPACING = 100.0
    Y_SPACING = 100.0
    CONTOURS -> Generalizer_2
    <REJECTED> -> SurfaceModeller__Rejected_

Bookmark: Lissage des géométries
Generalizer_2
    ALG_TEXT = Douglas (Generalize)
    PRESERVE = No
    PRESERVE_PATHS = No
    TOLERANCE = 10
    -> AreaBuilder_2
    <REJECTED> -> Generalizer_2__Rejected_
Generalizer_2__Rejected_: Logger
    LOG_FEATURE = LOG_ONLY
    MAXCOORDS = 20
    MAXFEATS = 20
    MESSAGE = Feature is:
    SEVERITY = INFO

Bookmark: Création de polygones
AreaBuilder_2
    ALLOW_CYCLES = No
    CHECK_CURVE_DIRECTION = No
    CONNECT_Z_MODE = First Wins
    CONSIDER_NODE_ELEVATION = no
    DEAGGREGATE_INPUT = Deaggregate
    DONUT_CREATION = Yes
    DROP_HOLES = No
    LINES_AS_SEGMENTS = No
    POLY_ACCUM_ATTRS_NAME = Use Attributes From One Feature
    SNAPTYPE_PARAM = None
    AREA -> nuage_de_points (writer POSTGIS_5)
    <REJECTED> -> AreaBuilder_2__Rejected_

Bookmark: Résultat en postgis
nuage_de_points (writer POSTGIS_5)
    attributes: _elevation float8
